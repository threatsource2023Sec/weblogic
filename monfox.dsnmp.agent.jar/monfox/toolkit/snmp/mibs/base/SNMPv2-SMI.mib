SNMPv2-SMI DEFINITIONS ::= 
BEGIN

   org ::= { iso  3 }

   dod ::= { org  6 }

   internet ::= { dod  1 }

   directory ::= { internet  1 }

   mgmt ::= { internet  2 }

   mib-2 ::= { mgmt  1 }

   transmission ::= { mib-2  10 }

   experimental ::= { internet  3 }

   private ::= { internet  4 }

   enterprises ::= { private  1 }

   security ::= { internet  5 }

   snmpV2 ::= { internet  6 }

   snmpDomains ::= { snmpV2  1 }

   snmpProxys ::= { snmpV2  2 }

   snmpModules ::= { snmpV2  3 }

   ObjectName ::=
       OBJECT IDENTIFIER

   NotificationName ::=
       OBJECT IDENTIFIER

   --ObjectSyntax ::=
   --    CHOICE {
   --        simple
   --            SimpleSyntax,
   --
   --        application-wide
   --            ApplicationSyntax
   --}

   --SimpleSyntax ::=
   --    CHOICE {
   --        integer-value
   --            INTEGER,
   --
   --        string-value
   --            OCTET STRING,
   --
   --        objectID-value
   --            OBJECT IDENTIFIER
   --}

   --Integer32 ::=
   --    [UNIVERSAL 2]
   --    IMPLICIT INTEGER

   --ApplicationSyntax ::=
   --    CHOICE {
   --        ipAddress-value
   --            IpAddress,
   --
   --        counter-value
   --            Counter32,
   --
   --        timeticks-value
   --            TimeTicks,
   --
   --        arbitrary-value
   --            Opaque,
   --
   --        big-counter-value
   --            Counter64,
   --
   --        unsigned-integer-value
   --            Unsigned32
   --}

   --IpAddress ::=
   --    [APPLICATION 0]
   --    IMPLICIT OCTET STRING

   --Counter32 ::=
   --    [APPLICATION 1]
   --    IMPLICIT INTEGER

   --Gauge32 ::=
   --    [APPLICATION 2]
   --    IMPLICIT INTEGER

   --Unsigned32 ::=
   --    [APPLICATION 2]
   --    IMPLICIT INTEGER

   --TimeTicks ::=
   --    [APPLICATION 3]
   --    IMPLICIT INTEGER

   --Opaque ::=
   --    [APPLICATION 4]
   --    IMPLICIT OCTET STRING

   --Counter64 ::=
   --    [APPLICATION 6]
   --    IMPLICIT INTEGER

   zeroDotZero OBJECT-IDENTITY
       STATUS       current
       DESCRIPTION
	   "A value used for null identifiers."
       ::= { 0  0 }

END
